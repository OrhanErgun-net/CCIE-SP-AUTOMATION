module vlan {

    yang-version 1.1;
    namespace "http://orhanergun.net/vlan";
    prefix vlan;

    import ietf-inet-types {
        prefix inet;
    }
    import tailf-ncs {
        prefix ncs;
    }
    import tailf-common {
        prefix tailf;
    }

    augment "/ncs:services" {

        list vlan {
            key name;

            uses ncs:service-data;
            ncs:servicepoint "vlan";

            leaf name {
                tailf:info "Service Instance Name";
                type string;
            }

            leaf vlan-id {
                tailf:info "Unique Vlan Id";
                mandatory true;
                type uint32 {
                    range "1..4094";
                }
            }

            leaf mode {
                tailf:info "Vlan Mode can be access | trunk";
                type enumeration {
                    enum access;
                    enum trunk;
                }
            }

            list device {
                key "name";

                leaf name {
                    tailf:info "Switch Name";
                    type leafref {
                        path "/ncs:devices/ncs:device/ncs:name";
                    }
                }

                list interface {
                    key "intf-type intf-id";

                    leaf intf-type {
                        tailf:info "Interface Type";
                        type enumeration {
                            enum "FastEthernet";
                            enum "GigabitEthernet";
                        }
                    }

                    leaf intf-id {
                        tailf:info "Interface Id";
                        type string {
                            pattern
                              "1/[1-9][0-9]{0,1}";
                        }
                    }
                }
            }
        }
    }
}
